import Draft
Gui.activateWorkbench("DraftWorkbench")
pl = App.Placement(App.Vector(250,0,0),App.Rotation(App.Vector(0,1,0),-45))
rec = Draft.makeRectangle(length=87,height=100,placement=pl,face=True,support=None)
Draft.autogroup(rec)

Gui.activateWorkbench("CfdOFWorkbench")

import CfdMeshRefinement
CfdMeshRefinement.makeCfdMeshRefinement(App.ActiveDocument.Fusion_Mesh)
referenceList = []
referenceList.append(('Rectangle','Face1'))
FreeCAD.ActiveDocument.MeshRefinement.References = referenceList

FreeCAD.ActiveDocument.MeshRefinement.RelativeLength = 0.5
FreeCAD.ActiveDocument.MeshRefinement.RefinementThickness = '0 mm'
FreeCAD.ActiveDocument.MeshRefinement.NumberLayers = 1
FreeCAD.ActiveDocument.MeshRefinement.ExpansionRatio = 1.2
FreeCAD.ActiveDocument.MeshRefinement.FirstLayerHeight = '0 mm'
FreeCAD.ActiveDocument.MeshRefinement.RegionEdgeRefinement = 1.0
FreeCAD.ActiveDocument.MeshRefinement.Baffle = True
FreeCAD.ActiveDocument.MeshRefinement.Internal = False

import CfdFluidBoundary
import CfdTools
CfdTools.getActiveAnalysis().addObject(CfdFluidBoundary.makeCfdFluidBoundary())

bc = FreeCAD.ActiveDocument.CfdFluidBoundary003
bc.BoundaryType = 'baffle'
bc.BoundarySubType = 'porousBaffle'
bc.ThermalBoundaryType = 'fixedValue'
bc.VelocityIsCartesian = True
bc.Ux = '0 mm/s'
bc.Uy = '0 mm/s'
bc.Uz = '0 mm/s'
bc.VelocityMag = '0 mm/s'
bc.DirectionFace = ''
bc.ReverseNormal = False
bc.MassFlowRate = '0 kg/s'
bc.VolFlowRate = '0 mm^3/s'
bc.Pressure = '0 kg/(mm*s^2)'
bc.SlipRatio = '0 '
bc.Temperature = '293 K'
bc.HeatFlux = '0 kg/s^3'
bc.HeatTransferCoeff = '0 kg/(s^3*K)'
bc.TurbulenceInletSpecification = 'intensityAndLengthScale'
bc.TurbulentKineticEnergy = '10000 mm^2/s^2'
bc.SpecificDissipationRate = '57.3 deg/s'
bc.TurbulenceIntensity = '0.1 '
bc.TurbulenceLengthScale = '100 mm'
bc.PorousBaffleMethod = 'porousCoeff'
bc.PressureDropCoeff = '0.84 '
bc.ScreenWireDiameter = '0.1 mm'
bc.ScreenSpacing = '0 mm'
FreeCAD.ActiveDocument.CfdFluidBoundary003.Label = 'baffle'
FreeCAD.ActiveDocument.CfdFluidBoundary003.References = []
FreeCAD.ActiveDocument.CfdFluidBoundary003.References.append(('Rectangle', 'Face1'))
FreeCAD.ActiveDocument.recompute()
