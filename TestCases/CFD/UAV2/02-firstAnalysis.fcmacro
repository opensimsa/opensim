Gui.activateWorkbench("CfdOFWorkbench")

import CfdAnalysis
import CfdTools
analysis = CfdAnalysis.makeCfdAnalysis('CfdAnalysis')
CfdTools.setActiveAnalysis(analysis)
import CfdPhysicsSelection
analysis.addObject(CfdPhysicsSelection.makeCfdPhysicsSelection())
import CfdFluidMaterial
analysis.addObject(CfdFluidMaterial.makeCfdFluidMaterial('FluidProperties'))
import CfdInitialiseFlowField
analysis.addObject(CfdInitialiseFlowField.makeCfdInitialFlowField())
import CfdSolverFoam
analysis.addObject(CfdSolverFoam.makeCfdSolverFoam())

import CfdMesh
CfdMesh.makeCfdMesh('Compound_Mesh')
App.ActiveDocument.ActiveObject.Part = App.ActiveDocument.Compound
CfdTools.getActiveAnalysis().addObject(App.ActiveDocument.ActiveObject)

FreeCAD.ActiveDocument.Compound_Mesh.CharacteristicLengthMax = '100 mm'
FreeCAD.ActiveDocument.Compound_Mesh.MeshUtility = 'cfMesh'
FreeCAD.ActiveDocument.Compound_Mesh.ElementDimension = '3D'
FreeCAD.ActiveDocument.Compound_Mesh.CellsBetweenLevels = 3
FreeCAD.ActiveDocument.Compound_Mesh.EdgeRefinement = 1.0
FreeCAD.ActiveDocument.Compound_Mesh.PointInMesh = {'x': '0 mm', 'y': '0 mm', 'z': '0 mm'}

import CfdMeshRefinement
CfdMeshRefinement.makeCfdMeshRefinement(App.ActiveDocument.Compound_Mesh)
referenceList = []
referenceList.append(('Cut','Face1'))
referenceList.append(('Cut','Face2'))
referenceList.append(('Cut','Face3'))
referenceList.append(('Cut','Face4'))
referenceList.append(('Cut','Face5'))
referenceList.append(('Cut','Face6'))
referenceList.append(('Cut','Face7'))
referenceList.append(('Cut','Face8'))
referenceList.append(('Cut','Face9'))
referenceList.append(('Cut','Face10'))
referenceList.append(('Cut','Face11'))
referenceList.append(('Cut','Face12'))
referenceList.append(('Cut','Face13'))
referenceList.append(('Cut','Face14'))
referenceList.append(('Cut','Face15'))
referenceList.append(('Cut','Face16'))
referenceList.append(('Cut','Face17'))
referenceList.append(('Cut','Face18'))
referenceList.append(('Cut','Face19'))
referenceList.append(('Cut','Face20'))
referenceList.append(('Cut','Face21'))
referenceList.append(('Cut','Face22'))
referenceList.append(('Cut','Face23'))
referenceList.append(('Cut','Face24'))
referenceList.append(('Cut','Face25'))
referenceList.append(('Cut','Face26'))
referenceList.append(('Cut','Face27'))
referenceList.append(('Cut','Face28'))
referenceList.append(('Cut','Face29'))
referenceList.append(('Cut','Face30'))
referenceList.append(('Cut','Face31'))
referenceList.append(('Cut','Face32'))
referenceList.append(('Cut','Face33'))
referenceList.append(('Cut','Face34'))
referenceList.append(('Cut','Face35'))
referenceList.append(('Cut','Face36'))
referenceList.append(('Cut','Face37'))
referenceList.append(('Cut','Face38'))
referenceList.append(('Cut','Face39'))
referenceList.append(('Cut','Face40'))
referenceList.append(('Cut','Face41'))
referenceList.append(('Cut','Face42'))
referenceList.append(('Cut','Face43'))
referenceList.append(('Cut','Face44'))
referenceList.append(('Cut','Face45'))
referenceList.append(('Cut','Face46'))
referenceList.append(('Cut','Face47'))
referenceList.append(('Cut','Face48'))
referenceList.append(('Cut','Face49'))
referenceList.append(('Cut','Face50'))
referenceList.append(('Cut','Face51'))
referenceList.append(('Cut','Face52'))
referenceList.append(('Cut','Face53'))
referenceList.append(('Cut','Face54'))
referenceList.append(('Cut','Face55'))
referenceList.append(('Cut','Face56'))
referenceList.append(('Cut','Face57'))
referenceList.append(('Cut','Face58'))
referenceList.append(('Cut','Face59'))
referenceList.append(('Cut','Face60'))
referenceList.append(('Cut','Face61'))
referenceList.append(('Cut','Face62'))
referenceList.append(('Cut','Face63'))
referenceList.append(('Cut','Face64'))
referenceList.append(('Cut','Face65'))
referenceList.append(('Cut','Face66'))
referenceList.append(('Cut','Face67'))
referenceList.append(('Cut','Face68'))
referenceList.append(('Cut','Face69'))
referenceList.append(('Cut','Face70'))
referenceList.append(('Cut','Face71'))
referenceList.append(('Cut','Face72'))
referenceList.append(('Cut','Face73'))
referenceList.append(('Cut','Face74'))
referenceList.append(('Cut','Face75'))
referenceList.append(('Cut','Face76'))
FreeCAD.ActiveDocument.MeshRefinement.References = referenceList

FreeCAD.ActiveDocument.MeshRefinement.RelativeLength = 0.25
FreeCAD.ActiveDocument.MeshRefinement.RefinementThickness = '100 mm'
FreeCAD.ActiveDocument.MeshRefinement.NumberLayers = 1
FreeCAD.ActiveDocument.MeshRefinement.ExpansionRatio = 1.2
FreeCAD.ActiveDocument.MeshRefinement.FirstLayerHeight = '0 mm'
FreeCAD.ActiveDocument.MeshRefinement.RegionEdgeRefinement = 1.0
FreeCAD.ActiveDocument.MeshRefinement.Internal = False

Gui.ActiveDocument.getObject("Compound_Mesh").Visibility=False
Gui.ActiveDocument.getObject("Compound").Visibility=True

obj = FreeCAD.ActiveDocument.PhysicsModel
obj.Time = 'Steady'
obj.Flow = 'Incompressible'
obj.Thermal = 'None'
obj.Turbulence = 'RANS'
obj.TurbulenceModel = 'kOmegaSST'
obj.gx = '0 mm/s^2'
obj.gy = '-9810 mm/s^2'
obj.gz = '0 mm/s^2'

FreeCAD.ActiveDocument.FluidProperties.Material = {'Name': 'Air', 'Description': 'Standard air properties at 20 Degrees Celsius and 1 atm', 'Density': '1.20 kg/m^3', 'DynamicViscosity': '1.80e-5 kg/m/s', 'MolarMass': '0.0289643897748887 kg/mol', 'Cp': '1004.703 J/kg/K', 'SutherlandConstant': '1.4579326545176254e-06 kg/m/s/K^0.5', 'SutherlandTemperature': '110.4 K'}

import CfdFluidBoundary
CfdTools.getActiveAnalysis().addObject(CfdFluidBoundary.makeCfdFluidBoundary())

bc = FreeCAD.ActiveDocument.CfdFluidBoundary
bc.BoundaryType = 'constraint'
bc.BoundarySubType = 'symmetry'
bc.ThermalBoundaryType = 'fixedValue'
bc.VelocityIsCartesian = True
bc.Ux = '0 mm/s'
bc.Uy = '0 mm/s'
bc.Uz = '0 mm/s'
bc.VelocityMag = '0 mm/s'
bc.DirectionFace = ''
bc.ReverseNormal = False
bc.MassFlowRate = '0 kg/s'
bc.VolFlowRate = '0 mm^3/s'
bc.Pressure = '0 kg/(mm*s^2)'
bc.SlipRatio = '0 '
bc.Temperature = '293 K'
bc.HeatFlux = '0 kg/s^3'
bc.HeatTransferCoeff = '0 kg/(s^3*K)'
bc.TurbulenceInletSpecification = 'intensityAndLengthScale'
bc.TurbulentKineticEnergy = '10000 mm^2/s^2'
bc.SpecificDissipationRate = '57.3 deg/s'
bc.TurbulenceIntensity = '0.1 '
bc.TurbulenceLengthScale = '100 mm'
bc.PorousBaffleMethod = 'porousCoeff'
bc.PressureDropCoeff = '0 '
bc.ScreenWireDiameter = '0.1 mm'
bc.ScreenSpacing = '0 mm'
FreeCAD.ActiveDocument.CfdFluidBoundary.Label = 'constraint'
FreeCAD.ActiveDocument.CfdFluidBoundary.References = []
FreeCAD.ActiveDocument.CfdFluidBoundary.References.append(('Compound', 'Face1'))
FreeCAD.ActiveDocument.recompute()

CfdTools.getActiveAnalysis().addObject(CfdFluidBoundary.makeCfdFluidBoundary())

bc = FreeCAD.ActiveDocument.CfdFluidBoundary001
bc.BoundaryType = 'inlet'
bc.BoundarySubType = 'uniformVelocityInlet'
bc.ThermalBoundaryType = 'fixedValue'
bc.VelocityIsCartesian = True
bc.Ux = '0 mm/s'
bc.Uy = '5000 mm/s'
bc.Uz = '-20000 mm/s'
bc.VelocityMag = '0 mm/s'
bc.DirectionFace = ''
bc.ReverseNormal = True
bc.MassFlowRate = '0 kg/s'
bc.VolFlowRate = '0 mm^3/s'
bc.Pressure = '0 kg/(mm*s^2)'
bc.SlipRatio = '0 '
bc.Temperature = '293 K'
bc.HeatFlux = '0 kg/s^3'
bc.HeatTransferCoeff = '0 kg/(s^3*K)'
bc.TurbulenceInletSpecification = 'intensityAndLengthScale'
bc.TurbulentKineticEnergy = '10000 mm^2/s^2'
bc.SpecificDissipationRate = '57.3 deg/s'
bc.TurbulenceIntensity = '0.1 '
bc.TurbulenceLengthScale = '100 mm'
bc.PorousBaffleMethod = 'porousCoeff'
bc.PressureDropCoeff = '0 '
bc.ScreenWireDiameter = '0.1 mm'
bc.ScreenSpacing = '0 mm'
FreeCAD.ActiveDocument.CfdFluidBoundary001.Label = 'inlet'
FreeCAD.ActiveDocument.CfdFluidBoundary001.References = []
FreeCAD.ActiveDocument.CfdFluidBoundary001.References.append(('Compound', 'Face3'))
FreeCAD.ActiveDocument.CfdFluidBoundary001.References.append(('Compound', 'Face6'))
FreeCAD.ActiveDocument.recompute()


CfdTools.getActiveAnalysis().addObject(CfdFluidBoundary.makeCfdFluidBoundary())

bc = FreeCAD.ActiveDocument.CfdFluidBoundary002
bc.BoundaryType = 'wall'
bc.BoundarySubType = 'slipWall'
bc.ThermalBoundaryType = 'fixedValue'
bc.VelocityIsCartesian = True
bc.Ux = '0 mm/s'
bc.Uy = '0 mm/s'
bc.Uz = '0 mm/s'
bc.VelocityMag = '0 mm/s'
bc.DirectionFace = ''
bc.ReverseNormal = False
bc.MassFlowRate = '0 kg/s'
bc.VolFlowRate = '0 mm^3/s'
bc.Pressure = '0 kg/(mm*s^2)'
bc.SlipRatio = '0 '
bc.Temperature = '293 K'
bc.HeatFlux = '0 kg/s^3'
bc.HeatTransferCoeff = '0 kg/(s^3*K)'
bc.TurbulenceInletSpecification = 'intensityAndLengthScale'
bc.TurbulentKineticEnergy = '10000 mm^2/s^2'
bc.SpecificDissipationRate = '57.3 deg/s'
bc.TurbulenceIntensity = '0.1 '
bc.TurbulenceLengthScale = '100 mm'
bc.PorousBaffleMethod = 'porousCoeff'
bc.PressureDropCoeff = '0 '
bc.ScreenWireDiameter = '0.1 mm'
bc.ScreenSpacing = '0 mm'
FreeCAD.ActiveDocument.CfdFluidBoundary002.Label = 'slip'
FreeCAD.ActiveDocument.CfdFluidBoundary002.References = []
FreeCAD.ActiveDocument.CfdFluidBoundary002.References.append(('Compound', 'Face2'))
FreeCAD.ActiveDocument.recompute()

CfdTools.getActiveAnalysis().addObject(CfdFluidBoundary.makeCfdFluidBoundary())

bc = FreeCAD.ActiveDocument.CfdFluidBoundary003
bc.BoundaryType = 'outlet'
bc.BoundarySubType = 'staticPressureOutlet'
bc.ThermalBoundaryType = 'fixedValue'
bc.VelocityIsCartesian = True
bc.Ux = '0 mm/s'
bc.Uy = '0 mm/s'
bc.Uz = '0 mm/s'
bc.VelocityMag = '0 mm/s'
bc.DirectionFace = ''
bc.ReverseNormal = False
bc.MassFlowRate = '0 kg/s'
bc.VolFlowRate = '0 mm^3/s'
bc.Pressure = '0 kg/(mm*s^2)'
bc.SlipRatio = '0 '
bc.Temperature = '293 K'
bc.HeatFlux = '0 kg/s^3'
bc.HeatTransferCoeff = '0 kg/(s^3*K)'
bc.TurbulenceInletSpecification = 'intensityAndLengthScale'
bc.TurbulentKineticEnergy = '10000 mm^2/s^2'
bc.SpecificDissipationRate = '57.3 deg/s'
bc.TurbulenceIntensity = '0.1 '
bc.TurbulenceLengthScale = '100 mm'
bc.PorousBaffleMethod = 'porousCoeff'
bc.PressureDropCoeff = '0 '
bc.ScreenWireDiameter = '0.1 mm'
bc.ScreenSpacing = '0 mm'
FreeCAD.ActiveDocument.CfdFluidBoundary003.Label = 'outlet'
FreeCAD.ActiveDocument.CfdFluidBoundary003.References = []
FreeCAD.ActiveDocument.CfdFluidBoundary003.References.append(('Compound', 'Face4'))
FreeCAD.ActiveDocument.CfdFluidBoundary003.References.append(('Compound', 'Face5'))
FreeCAD.ActiveDocument.recompute()

Gui.ActiveDocument.getObject("Compound").Visibility=True
Gui.ActiveDocument.getObject("Shell").Visibility=False

CfdTools.getActiveAnalysis().addObject(CfdFluidBoundary.makeCfdFluidBoundary())

bc = FreeCAD.ActiveDocument.CfdFluidBoundary004
bc.BoundaryType = 'wall'
bc.BoundarySubType = 'fixedWall'
bc.ThermalBoundaryType = 'fixedValue'
bc.VelocityIsCartesian = True
bc.Ux = '0 mm/s'
bc.Uy = '0 mm/s'
bc.Uz = '0 mm/s'
bc.VelocityMag = '0 mm/s'
bc.DirectionFace = ''
bc.ReverseNormal = False
bc.MassFlowRate = '0 kg/s'
bc.VolFlowRate = '0 mm^3/s'
bc.Pressure = '0 kg/(mm*s^2)'
bc.SlipRatio = '0 '
bc.Temperature = '293 K'
bc.HeatFlux = '0 kg/s^3'
bc.HeatTransferCoeff = '0 kg/(s^3*K)'
bc.TurbulenceInletSpecification = 'intensityAndLengthScale'
bc.TurbulentKineticEnergy = '10000 mm^2/s^2'
bc.SpecificDissipationRate = '57.3 deg/s'
bc.TurbulenceIntensity = '0.1 '
bc.TurbulenceLengthScale = '100 mm'
bc.PorousBaffleMethod = 'porousCoeff'
bc.PressureDropCoeff = '0 '
bc.ScreenWireDiameter = '0.1 mm'
bc.ScreenSpacing = '0 mm'
FreeCAD.ActiveDocument.CfdFluidBoundary004.Label = 'wall'
referenceList = []
referenceList.append(('Cut','Face1'))
referenceList.append(('Cut','Face2'))
referenceList.append(('Cut','Face3'))
referenceList.append(('Cut','Face4'))
referenceList.append(('Cut','Face5'))
referenceList.append(('Cut','Face6'))
referenceList.append(('Cut','Face7'))
referenceList.append(('Cut','Face8'))
referenceList.append(('Cut','Face9'))
referenceList.append(('Cut','Face10'))
referenceList.append(('Cut','Face11'))
referenceList.append(('Cut','Face12'))
referenceList.append(('Cut','Face13'))
referenceList.append(('Cut','Face14'))
referenceList.append(('Cut','Face15'))
referenceList.append(('Cut','Face16'))
referenceList.append(('Cut','Face17'))
referenceList.append(('Cut','Face18'))
referenceList.append(('Cut','Face19'))
referenceList.append(('Cut','Face20'))
referenceList.append(('Cut','Face21'))
referenceList.append(('Cut','Face22'))
referenceList.append(('Cut','Face23'))
referenceList.append(('Cut','Face24'))
referenceList.append(('Cut','Face25'))
referenceList.append(('Cut','Face26'))
referenceList.append(('Cut','Face27'))
referenceList.append(('Cut','Face28'))
referenceList.append(('Cut','Face29'))
referenceList.append(('Cut','Face30'))
referenceList.append(('Cut','Face31'))
referenceList.append(('Cut','Face32'))
referenceList.append(('Cut','Face33'))
referenceList.append(('Cut','Face34'))
referenceList.append(('Cut','Face35'))
referenceList.append(('Cut','Face36'))
referenceList.append(('Cut','Face37'))
referenceList.append(('Cut','Face38'))
referenceList.append(('Cut','Face39'))
referenceList.append(('Cut','Face40'))
referenceList.append(('Cut','Face41'))
referenceList.append(('Cut','Face42'))
referenceList.append(('Cut','Face43'))
referenceList.append(('Cut','Face44'))
referenceList.append(('Cut','Face45'))
referenceList.append(('Cut','Face46'))
referenceList.append(('Cut','Face47'))
referenceList.append(('Cut','Face48'))
referenceList.append(('Cut','Face49'))
referenceList.append(('Cut','Face50'))
referenceList.append(('Cut','Face51'))
referenceList.append(('Cut','Face52'))
referenceList.append(('Cut','Face53'))
referenceList.append(('Cut','Face54'))
referenceList.append(('Cut','Face55'))
referenceList.append(('Cut','Face56'))
referenceList.append(('Cut','Face57'))
referenceList.append(('Cut','Face58'))
referenceList.append(('Cut','Face59'))
referenceList.append(('Cut','Face60'))
referenceList.append(('Cut','Face61'))
referenceList.append(('Cut','Face62'))
referenceList.append(('Cut','Face63'))
referenceList.append(('Cut','Face64'))
referenceList.append(('Cut','Face65'))
referenceList.append(('Cut','Face66'))
referenceList.append(('Cut','Face67'))
referenceList.append(('Cut','Face68'))
referenceList.append(('Cut','Face69'))
referenceList.append(('Cut','Face70'))
referenceList.append(('Cut','Face71'))
referenceList.append(('Cut','Face72'))
referenceList.append(('Cut','Face73'))
referenceList.append(('Cut','Face74'))
referenceList.append(('Cut','Face75'))
referenceList.append(('Cut','Face76'))
FreeCAD.ActiveDocument.CfdFluidBoundary004.References = referenceList
FreeCAD.ActiveDocument.recompute()

init = FreeCAD.ActiveDocument.InitialiseFields
init.PotentialFlow = True
init.UseInletUValues = False
init.Ux = '0 mm/s'
init.Uy = '0 mm/s'
init.Uz = '0 mm/s'
init.UseOutletPValue = True
init.BoundaryP = FreeCAD.ActiveDocument.CfdFluidBoundary003
init.Pressure = '0 kg/(mm*s^2)'
init.VolumeFractions = {}
init.UseInletTemperatureValue = False
init.Temperature = '293 K'
init.UseInletTurbulenceValues = False
init.omega = '1 rad/s'
init.k = '0.01 m^2/s^2'

FreeCAD.ActiveDocument.getObject("CfdSolver").Parallel = True
FreeCAD.ActiveDocument.getObject("CfdSolver").ParallelCores = 4
