# -*- coding: utf-8 -*-

# Macro Begin: macro\01-geom.FCMacro +++++++++++++++++++++++++++++++++++++++++++++++++
import FreeCAD
import Part
#import SplitFeatures
import BOPTools.SplitFeatures
import os

#Gui.activateWorkbench("ArchWorkbench")
#Gui.activateWorkbench("PartWorkbench")
doc = App.newDocument()
Part.insert(os.path.join(os.path.dirname(__file__), "..", "step", "uav.stp"), doc.Name)
App.ActiveDocument.addObject("Part::Box","Box")
App.ActiveDocument.ActiveObject.Label = "Cube"
App.ActiveDocument.recompute()
#Gui.SendMsgToActiveView("ViewFit")
App.ActiveDocument.getObject("Box").Length = '15000 mm'
App.ActiveDocument.getObject("Box").Width = '10000 mm'
App.ActiveDocument.getObject("Box").Height = '10000 mm'
App.ActiveDocument.getObject("Box").Placement = App.Placement(App.Vector(-7000,-4000,0),App.Rotation(App.Vector(0,0,1),0))
#Gui.activeDocument().activeView().viewBottom()
Gui.activeDocument().getObject("Box").Transparency = 50
j = BOPTools.SplitFeatures.makeXOR(name= 'XOR')
j.Objects = [App.ActiveDocument.Box, App.ActiveDocument.uav]
j.Proxy.execute(j)
j.purgeTouched()
for obj in j.ViewObject.Proxy.claimChildren():
    obj.ViewObject.hide()
Gui.activeDocument().activeView().setCameraType("Perspective")
# Macro End: macro\01-geom.FCMacro +++++++++++++++++++++++++++++++++++++++++++++++++
