# -*- coding: utf-8 -*-

# Macro Begin: /ntfs/projects/FreeCAD/macros/03-boundary.FCMacro +++++++++++++++++++++++++++++++++++++++++++++++++
import FreeCAD
import _CommandCfdFluidBoundary
import FemGui
import CfdFluidBoundary

obj = FreeCAD.ActiveDocument.PhysicsModel
obj.Time = 'Steady'
obj.Phase = 'Single'
obj.Flow = 'Incompressible'
obj.Thermal = 'None'
obj.Turbulence = 'RANS'
obj.TurbulenceModel = 'kOmegaSST'

mat = FreeCAD.ActiveDocument.FluidProperties.Material
mat['Density'] = '1.2e-09 kg/mm^3'
mat['DynamicViscosity'] = '1.8e-08 kg/(mm*s)'
FreeCAD.ActiveDocument.FluidProperties.Material = mat

# Values are converted to SI units and stored (eg. m/s)
init = FreeCAD.ActiveDocument.InitialiseFields.InitialVariables
init['PotentialFoam'] = True
init['Ux'] = 0.0
init['Uy'] = 0.0
init['Uz'] = 0.0
init['Pressure'] = 0.0
init['UseInletTurbulenceValues'] = False
init['omega'] = 1.00007366139
init['k'] = 0.01
FreeCAD.ActiveDocument.InitialiseFields.InitialVariables = init
#Gui.activateWorkbench("CfdOFWorkbench")
FemGui.getActiveAnalysis().addObject(CfdFluidBoundary.makeCfdFluidBoundary())

# Values are converted to SI units and stored (eg. m/s)
bc = FreeCAD.ActiveDocument.CfdFluidBoundary.BoundarySettings
bc['BoundaryType'] = 'inlet'
bc['BoundarySubtype'] = 'uniformVelocity'
bc['ThermalBoundaryType'] = 'fixedValue'
bc['VelocityIsCartesian'] = True
bc['Ux'] = 20.0
bc['Uy'] = 0.0
bc['Uz'] = 0.0
bc['VelocityMag'] = 0.0
bc['DirectionFace'] = ''
bc['ReverseNormal'] = True
bc['MassFlowRate'] = 0.0
bc['VolFlowRate'] = 0.0
bc['Pressure'] = 0.0
bc['SlipRatio'] = 0.0
bc['TurbulenceInletSpecification'] = 'intensityAndLengthScale'
bc['TurbulentKineticEnergy'] = 0.01
bc['SpecificDissipationRate'] = 1.00007366139
bc['TurbulenceIntensity'] = 0.1
bc['TurbulenceLengthScale'] = 0.1
bc['PressureDropCoeff'] = 0.0
bc['ScreenWireDiameter'] = 0.0001
bc['ScreenSpacing'] = 0.0
bc['PorousBaffleMethod'] = 0
FreeCAD.ActiveDocument.CfdFluidBoundary.BoundarySettings = bc
FreeCAD.ActiveDocument.CfdFluidBoundary.Label = 'inlet'
FreeCAD.ActiveDocument.CfdFluidBoundary.References = []
FreeCAD.ActiveDocument.CfdFluidBoundary.References.append(('Box', 'Face1'))
FreeCAD.ActiveDocument.recompute()
FemGui.getActiveAnalysis().addObject(CfdFluidBoundary.makeCfdFluidBoundary())

# Values are converted to SI units and stored (eg. m/s)
bc = FreeCAD.ActiveDocument.CfdFluidBoundary001.BoundarySettings
bc['BoundaryType'] = 'outlet'
bc['BoundarySubtype'] = 'staticPressure'
bc['ThermalBoundaryType'] = 'fixedValue'
bc['VelocityIsCartesian'] = True
bc['Ux'] = 0.0
bc['Uy'] = 0.0
bc['Uz'] = 0.0
bc['VelocityMag'] = 0.0
bc['DirectionFace'] = ''
bc['ReverseNormal'] = False
bc['MassFlowRate'] = 0.0
bc['VolFlowRate'] = 0.0
bc['Pressure'] = 0.0
bc['SlipRatio'] = 0.0
bc['TurbulenceInletSpecification'] = 'intensityAndLengthScale'
bc['TurbulentKineticEnergy'] = 0.01
bc['SpecificDissipationRate'] = 1.00007366139
bc['TurbulenceIntensity'] = 0.1
bc['TurbulenceLengthScale'] = 0.1
bc['PressureDropCoeff'] = 0.0
bc['ScreenWireDiameter'] = 0.0001
bc['ScreenSpacing'] = 0.0
bc['PorousBaffleMethod'] = 0
FreeCAD.ActiveDocument.CfdFluidBoundary001.BoundarySettings = bc
FreeCAD.ActiveDocument.CfdFluidBoundary001.Label = 'outlet'
FreeCAD.ActiveDocument.CfdFluidBoundary001.References = []
FreeCAD.ActiveDocument.CfdFluidBoundary001.References.append(('Box', 'Face2'))
FreeCAD.ActiveDocument.recompute()
FemGui.getActiveAnalysis().addObject(CfdFluidBoundary.makeCfdFluidBoundary())

# Values are converted to SI units and stored (eg. m/s)
bc = FreeCAD.ActiveDocument.CfdFluidBoundary002.BoundarySettings
bc['BoundaryType'] = 'wall'
bc['BoundarySubtype'] = 'slip'
bc['ThermalBoundaryType'] = 'fixedValue'
bc['VelocityIsCartesian'] = True
bc['Ux'] = 0.0
bc['Uy'] = 0.0
bc['Uz'] = 0.0
bc['VelocityMag'] = 0.0
bc['DirectionFace'] = ''
bc['ReverseNormal'] = False
bc['MassFlowRate'] = 0.0
bc['VolFlowRate'] = 0.0
bc['Pressure'] = 0.0
bc['SlipRatio'] = 0.0
bc['TurbulenceInletSpecification'] = 'intensityAndLengthScale'
bc['TurbulentKineticEnergy'] = 0.01
bc['SpecificDissipationRate'] = 1.00007366139
bc['TurbulenceIntensity'] = 0.1
bc['TurbulenceLengthScale'] = 0.1
bc['PressureDropCoeff'] = 0.0
bc['ScreenWireDiameter'] = 0.0001
bc['ScreenSpacing'] = 0.0
bc['PorousBaffleMethod'] = 0
FreeCAD.ActiveDocument.CfdFluidBoundary002.BoundarySettings = bc
FreeCAD.ActiveDocument.CfdFluidBoundary002.Label = 'wall'
FreeCAD.ActiveDocument.CfdFluidBoundary002.References = []
FreeCAD.ActiveDocument.CfdFluidBoundary002.References.append(('Box', 'Face6'))
FreeCAD.ActiveDocument.CfdFluidBoundary002.References.append(('Box', 'Face4'))
FreeCAD.ActiveDocument.CfdFluidBoundary002.References.append(('Box', 'Face3'))
FreeCAD.ActiveDocument.recompute()
FemGui.getActiveAnalysis().addObject(CfdFluidBoundary.makeCfdFluidBoundary())

# Values are converted to SI units and stored (eg. m/s)
bc = FreeCAD.ActiveDocument.CfdFluidBoundary003.BoundarySettings
bc['BoundaryType'] = 'constraint'
bc['BoundarySubtype'] = 'symmetry'
bc['ThermalBoundaryType'] = 'fixedValue'
bc['VelocityIsCartesian'] = True
bc['Ux'] = 0.0
bc['Uy'] = 0.0
bc['Uz'] = 0.0
bc['VelocityMag'] = 0.0
bc['DirectionFace'] = ''
bc['ReverseNormal'] = False
bc['MassFlowRate'] = 0.0
bc['VolFlowRate'] = 0.0
bc['Pressure'] = 0.0
bc['SlipRatio'] = 0.0
bc['TurbulenceInletSpecification'] = 'intensityAndLengthScale'
bc['TurbulentKineticEnergy'] = 0.01
bc['SpecificDissipationRate'] = 1.00007366139
bc['TurbulenceIntensity'] = 0.1
bc['TurbulenceLengthScale'] = 0.1
bc['PressureDropCoeff'] = 0.0
bc['ScreenWireDiameter'] = 0.0001
bc['ScreenSpacing'] = 0.0
bc['PorousBaffleMethod'] = 0
FreeCAD.ActiveDocument.CfdFluidBoundary003.BoundarySettings = bc
FreeCAD.ActiveDocument.CfdFluidBoundary003.Label = 'constraint'
FreeCAD.ActiveDocument.CfdFluidBoundary003.References = []
FreeCAD.ActiveDocument.CfdFluidBoundary003.References.append(('XOR', 'Face89'))
FreeCAD.ActiveDocument.recompute()
FemGui.getActiveAnalysis().addObject(CfdFluidBoundary.makeCfdFluidBoundary())

# Values are converted to SI units and stored (eg. m/s)
bc = FreeCAD.ActiveDocument.CfdFluidBoundary004.BoundarySettings
bc['BoundaryType'] = 'wall'
bc['BoundarySubtype'] = 'fixed'
bc['ThermalBoundaryType'] = 'fixedValue'
bc['VelocityIsCartesian'] = True
bc['Ux'] = 0.0
bc['Uy'] = 0.0
bc['Uz'] = 0.0
bc['VelocityMag'] = 0.0
bc['DirectionFace'] = ''
bc['ReverseNormal'] = False
bc['MassFlowRate'] = 0.0
bc['VolFlowRate'] = 0.0
bc['Pressure'] = 0.0
bc['SlipRatio'] = 0.0
bc['TurbulenceInletSpecification'] = 'intensityAndLengthScale'
bc['TurbulentKineticEnergy'] = 0.01
bc['SpecificDissipationRate'] = 1.00007366139
bc['TurbulenceIntensity'] = 0.1
bc['TurbulenceLengthScale'] = 0.1
bc['PressureDropCoeff'] = 0.0
bc['ScreenWireDiameter'] = 0.0001
bc['ScreenSpacing'] = 0.0
bc['PorousBaffleMethod'] = 0
FreeCAD.ActiveDocument.CfdFluidBoundary004.BoundarySettings = bc
FreeCAD.ActiveDocument.CfdFluidBoundary004.Label = 'wall001'
FreeCAD.ActiveDocument.CfdFluidBoundary004.References = []
FreeCAD.ActiveDocument.CfdFluidBoundary004.References.append(('uav', 'Face1'))
FreeCAD.ActiveDocument.CfdFluidBoundary004.References.append(('uav', 'Face2'))
FreeCAD.ActiveDocument.CfdFluidBoundary004.References.append(('uav', 'Face3'))
FreeCAD.ActiveDocument.CfdFluidBoundary004.References.append(('uav', 'Face4'))
FreeCAD.ActiveDocument.CfdFluidBoundary004.References.append(('uav', 'Face5'))
FreeCAD.ActiveDocument.CfdFluidBoundary004.References.append(('uav', 'Face6'))
FreeCAD.ActiveDocument.CfdFluidBoundary004.References.append(('uav', 'Face7'))
FreeCAD.ActiveDocument.CfdFluidBoundary004.References.append(('uav', 'Face8'))
FreeCAD.ActiveDocument.CfdFluidBoundary004.References.append(('uav', 'Face9'))
FreeCAD.ActiveDocument.CfdFluidBoundary004.References.append(('uav', 'Face10'))
FreeCAD.ActiveDocument.CfdFluidBoundary004.References.append(('uav', 'Face11'))
FreeCAD.ActiveDocument.CfdFluidBoundary004.References.append(('uav', 'Face12'))
FreeCAD.ActiveDocument.CfdFluidBoundary004.References.append(('uav', 'Face13'))
FreeCAD.ActiveDocument.CfdFluidBoundary004.References.append(('uav', 'Face14'))
FreeCAD.ActiveDocument.CfdFluidBoundary004.References.append(('uav', 'Face15'))
FreeCAD.ActiveDocument.CfdFluidBoundary004.References.append(('uav', 'Face16'))
FreeCAD.ActiveDocument.CfdFluidBoundary004.References.append(('uav', 'Face17'))
FreeCAD.ActiveDocument.CfdFluidBoundary004.References.append(('uav', 'Face18'))
FreeCAD.ActiveDocument.CfdFluidBoundary004.References.append(('uav', 'Face19'))
FreeCAD.ActiveDocument.CfdFluidBoundary004.References.append(('uav', 'Face20'))
FreeCAD.ActiveDocument.CfdFluidBoundary004.References.append(('uav', 'Face21'))
FreeCAD.ActiveDocument.CfdFluidBoundary004.References.append(('uav', 'Face22'))
FreeCAD.ActiveDocument.CfdFluidBoundary004.References.append(('uav', 'Face23'))
FreeCAD.ActiveDocument.CfdFluidBoundary004.References.append(('uav', 'Face24'))
FreeCAD.ActiveDocument.CfdFluidBoundary004.References.append(('uav', 'Face25'))
FreeCAD.ActiveDocument.CfdFluidBoundary004.References.append(('uav', 'Face26'))
FreeCAD.ActiveDocument.CfdFluidBoundary004.References.append(('uav', 'Face27'))
FreeCAD.ActiveDocument.CfdFluidBoundary004.References.append(('uav', 'Face28'))
FreeCAD.ActiveDocument.CfdFluidBoundary004.References.append(('uav', 'Face29'))
FreeCAD.ActiveDocument.CfdFluidBoundary004.References.append(('uav', 'Face30'))
FreeCAD.ActiveDocument.CfdFluidBoundary004.References.append(('uav', 'Face31'))
FreeCAD.ActiveDocument.CfdFluidBoundary004.References.append(('uav', 'Face32'))
FreeCAD.ActiveDocument.CfdFluidBoundary004.References.append(('uav', 'Face33'))
FreeCAD.ActiveDocument.CfdFluidBoundary004.References.append(('uav', 'Face34'))
FreeCAD.ActiveDocument.CfdFluidBoundary004.References.append(('uav', 'Face35'))
FreeCAD.ActiveDocument.CfdFluidBoundary004.References.append(('uav', 'Face36'))
FreeCAD.ActiveDocument.CfdFluidBoundary004.References.append(('uav', 'Face37'))
FreeCAD.ActiveDocument.CfdFluidBoundary004.References.append(('uav', 'Face38'))
FreeCAD.ActiveDocument.CfdFluidBoundary004.References.append(('uav', 'Face39'))
FreeCAD.ActiveDocument.CfdFluidBoundary004.References.append(('uav', 'Face40'))
FreeCAD.ActiveDocument.CfdFluidBoundary004.References.append(('uav', 'Face41'))
FreeCAD.ActiveDocument.CfdFluidBoundary004.References.append(('uav', 'Face42'))
FreeCAD.ActiveDocument.CfdFluidBoundary004.References.append(('uav', 'Face43'))
FreeCAD.ActiveDocument.CfdFluidBoundary004.References.append(('uav', 'Face44'))
FreeCAD.ActiveDocument.CfdFluidBoundary004.References.append(('uav', 'Face45'))
FreeCAD.ActiveDocument.CfdFluidBoundary004.References.append(('uav', 'Face46'))
FreeCAD.ActiveDocument.CfdFluidBoundary004.References.append(('uav', 'Face47'))
FreeCAD.ActiveDocument.CfdFluidBoundary004.References.append(('uav', 'Face48'))
FreeCAD.ActiveDocument.CfdFluidBoundary004.References.append(('uav', 'Face49'))
FreeCAD.ActiveDocument.CfdFluidBoundary004.References.append(('uav', 'Face50'))
FreeCAD.ActiveDocument.CfdFluidBoundary004.References.append(('uav', 'Face51'))
FreeCAD.ActiveDocument.CfdFluidBoundary004.References.append(('uav', 'Face52'))
FreeCAD.ActiveDocument.CfdFluidBoundary004.References.append(('uav', 'Face53'))
FreeCAD.ActiveDocument.CfdFluidBoundary004.References.append(('uav', 'Face54'))
FreeCAD.ActiveDocument.CfdFluidBoundary004.References.append(('uav', 'Face55'))
FreeCAD.ActiveDocument.CfdFluidBoundary004.References.append(('uav', 'Face56'))
FreeCAD.ActiveDocument.CfdFluidBoundary004.References.append(('uav', 'Face57'))
FreeCAD.ActiveDocument.CfdFluidBoundary004.References.append(('uav', 'Face58'))
FreeCAD.ActiveDocument.CfdFluidBoundary004.References.append(('uav', 'Face59'))
FreeCAD.ActiveDocument.CfdFluidBoundary004.References.append(('uav', 'Face60'))
FreeCAD.ActiveDocument.CfdFluidBoundary004.References.append(('uav', 'Face61'))
FreeCAD.ActiveDocument.CfdFluidBoundary004.References.append(('uav', 'Face62'))
FreeCAD.ActiveDocument.recompute()
# Macro End: /ntfs/projects/FreeCAD/macros/03-boundary.FCMacro +++++++++++++++++++++++++++++++++++++++++++++++++
