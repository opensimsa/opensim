# -*- coding: utf-8 -*-

# Macro Begin: /ntfs/projects/FreeCAD/macros/04-meshRefine.FCMacro +++++++++++++++++++++++++++++++++++++++++++++++++
import FreeCAD

referenceList = []
referenceList.append(('uav','Face1'))
referenceList.append(('uav','Face2'))
referenceList.append(('uav','Face3'))
referenceList.append(('uav','Face4'))
referenceList.append(('uav','Face5'))
referenceList.append(('uav','Face6'))
referenceList.append(('uav','Face7'))
referenceList.append(('uav','Face8'))
referenceList.append(('uav','Face9'))
referenceList.append(('uav','Face10'))
referenceList.append(('uav','Face11'))
referenceList.append(('uav','Face12'))
referenceList.append(('uav','Face13'))
referenceList.append(('uav','Face14'))
referenceList.append(('uav','Face15'))
referenceList.append(('uav','Face16'))
referenceList.append(('uav','Face17'))
referenceList.append(('uav','Face18'))
referenceList.append(('uav','Face19'))
referenceList.append(('uav','Face20'))
referenceList.append(('uav','Face21'))
referenceList.append(('uav','Face22'))
referenceList.append(('uav','Face23'))
referenceList.append(('uav','Face24'))
referenceList.append(('uav','Face25'))
referenceList.append(('uav','Face26'))
referenceList.append(('uav','Face27'))
referenceList.append(('uav','Face28'))
referenceList.append(('uav','Face29'))
referenceList.append(('uav','Face30'))
referenceList.append(('uav','Face31'))
referenceList.append(('uav','Face32'))
referenceList.append(('uav','Face33'))
referenceList.append(('uav','Face34'))
referenceList.append(('uav','Face35'))
referenceList.append(('uav','Face36'))
referenceList.append(('uav','Face37'))
referenceList.append(('uav','Face38'))
referenceList.append(('uav','Face39'))
referenceList.append(('uav','Face40'))
referenceList.append(('uav','Face41'))
referenceList.append(('uav','Face42'))
referenceList.append(('uav','Face43'))
referenceList.append(('uav','Face44'))
referenceList.append(('uav','Face45'))
referenceList.append(('uav','Face46'))
referenceList.append(('uav','Face47'))
referenceList.append(('uav','Face48'))
referenceList.append(('uav','Face49'))
referenceList.append(('uav','Face50'))
referenceList.append(('uav','Face51'))
referenceList.append(('uav','Face52'))
referenceList.append(('uav','Face53'))
referenceList.append(('uav','Face54'))
referenceList.append(('uav','Face55'))
referenceList.append(('uav','Face56'))
referenceList.append(('uav','Face57'))
referenceList.append(('uav','Face58'))
referenceList.append(('uav','Face59'))
referenceList.append(('uav','Face60'))
referenceList.append(('uav','Face61'))
referenceList.append(('uav','Face62'))
FreeCAD.ActiveDocument.MeshRegion.References = referenceList

FreeCAD.ActiveDocument.MeshRegion.RelativeLength = 0.25
FreeCAD.ActiveDocument.MeshRegion.RefinementThickness = '0 mm'
FreeCAD.ActiveDocument.MeshRegion.NumberLayers = 4
FreeCAD.ActiveDocument.MeshRegion.ExpansionRatio = 1.15
FreeCAD.ActiveDocument.MeshRegion.FirstLayerHeight = '0 mm'
FreeCAD.ActiveDocument.MeshRegion.RefinementLevel = 1
FreeCAD.ActiveDocument.MeshRegion.RegionEdgeRefinement = 1
FreeCAD.ActiveDocument.MeshRegion.Baffle = False
referenceList = []
referenceList.append(('uav','Face1'))
referenceList.append(('uav','Face2'))
referenceList.append(('uav','Face5'))
referenceList.append(('uav','Face8'))
referenceList.append(('uav','Face10'))
referenceList.append(('uav','Face12'))
referenceList.append(('uav','Face14'))
referenceList.append(('uav','Face17'))
referenceList.append(('uav','Face18'))
referenceList.append(('uav','Face21'))
referenceList.append(('uav','Face22'))
referenceList.append(('uav','Face23'))
referenceList.append(('uav','Face24'))
referenceList.append(('uav','Face41'))
referenceList.append(('uav','Face42'))
referenceList.append(('uav','Face51'))
referenceList.append(('uav','Face55'))
referenceList.append(('uav','Face56'))
referenceList.append(('uav','Face57'))
referenceList.append(('uav','Face58'))
referenceList.append(('uav','Face59'))
referenceList.append(('uav','Face60'))
referenceList.append(('uav','Face62'))
FreeCAD.ActiveDocument.MeshRegion001.References = referenceList

FreeCAD.ActiveDocument.MeshRegion001.RelativeLength = 0.125
FreeCAD.ActiveDocument.MeshRegion001.RefinementThickness = '0 mm'
FreeCAD.ActiveDocument.MeshRegion001.NumberLayers = 4
FreeCAD.ActiveDocument.MeshRegion001.ExpansionRatio = 1.15
FreeCAD.ActiveDocument.MeshRegion001.FirstLayerHeight = '0 mm'
FreeCAD.ActiveDocument.MeshRegion001.RefinementLevel = 1
FreeCAD.ActiveDocument.MeshRegion001.RegionEdgeRefinement = 1
FreeCAD.ActiveDocument.MeshRegion001.Baffle = False

import CfdMeshRegion
CfdMeshRegion.makeCfdMeshRegion(App.ActiveDocument.XOR_CartesianMesh)
referenceList = []
FreeCAD.ActiveDocument.MeshRegion002.References = referenceList
FreeCAD.ActiveDocument.MeshRegion002.RelativeLength = 0.5
FreeCAD.ActiveDocument.MeshRegion002.RefinementThickness = '0 mm'
FreeCAD.ActiveDocument.MeshRegion002.NumberLayers = 0
FreeCAD.ActiveDocument.MeshRegion002.ExpansionRatio = 0.0
FreeCAD.ActiveDocument.MeshRegion002.FirstLayerHeight = '0 mm'
FreeCAD.ActiveDocument.MeshRegion002.RefinementLevel = 1
FreeCAD.ActiveDocument.MeshRegion002.RegionEdgeRefinement = 1
FreeCAD.ActiveDocument.MeshRegion002.Baffle = False
FreeCAD.ActiveDocument.MeshRegion002.Internal = True
FreeCAD.ActiveDocument.MeshRegion002.InternalRegion = {'BoxLengths': {'y': 2.0, 'x': 5.0, 'z': 6.0}, 'Type': 'Box', 'Center': {'y': 0.5, 'x': 1.0, 'z': 0}, 'SphereRadius': 0.001}

FreeCAD.ActiveDocument.getObject("OpenFOAM").Parallel = True
FreeCAD.ActiveDocument.getObject("OpenFOAM").ParallelCores = 4

# Macro End: /ntfs/projects/FreeCAD/macros/04-meshRefine.FCMacro +++++++++++++++++++++++++++++++++++++++++++++++++
