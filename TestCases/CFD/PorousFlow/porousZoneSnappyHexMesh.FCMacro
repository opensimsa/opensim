# -*- coding: utf-8 -*-

import os
FreeCAD.open(os.path.join(os.path.dirname(__file__), "porousZoneGeometry.fcstd"))

Gui.activateWorkbench("CfdOFWorkbench")
import CfdAnalysis
import CfdTools
analysis = CfdAnalysis.makeCfdAnalysis('CfdAnalysis')
CfdTools.setActiveAnalysis(analysis)
import CfdPhysicsSelection
analysis.addObject(CfdPhysicsSelection.makeCfdPhysicsSelection())
import CfdFluidMaterial
analysis.addObject(CfdFluidMaterial.makeCfdFluidMaterial('FluidProperties'))
import CfdInitialiseFlowField
analysis.addObject(CfdInitialiseFlowField.makeCfdInitialFlowField())
import CfdSolverFoam
analysis.addObject(CfdSolverFoam.makeCfdSolverFoam())

import CfdMesh
CfdMesh.makeCfdMesh('Box_Mesh')
App.ActiveDocument.ActiveObject.Part = App.ActiveDocument.Box
CfdTools.getActiveAnalysis().addObject(App.ActiveDocument.ActiveObject)

FreeCAD.ActiveDocument.Box_Mesh.CharacteristicLengthMax = '50 mm'
FreeCAD.ActiveDocument.Box_Mesh.MeshUtility = 'snappyHexMesh'
FreeCAD.ActiveDocument.Box_Mesh.ElementDimension = '3D'
FreeCAD.ActiveDocument.Box_Mesh.CellsBetweenLevels = 3
FreeCAD.ActiveDocument.Box_Mesh.EdgeRefinement = 1.0
FreeCAD.ActiveDocument.Box_Mesh.PointInMesh = {'x': '291 mm', 'y': '281.5 mm', 'z': '2395 mm'}

obj = FreeCAD.ActiveDocument.PhysicsModel
obj.Time = 'Steady'
obj.Flow = 'Incompressible'
obj.Thermal = 'None'
obj.Turbulence = 'Laminar'
obj.gx = '0 mm/s^2'
obj.gy = '-9810 mm/s^2'
obj.gz = '0 mm/s^2'

FreeCAD.ActiveDocument.FluidProperties.Material = {'Name': 'Air', 'Description': 'Standard air properties at 20 Degrees Celsius and 1 atm', 'Density': '1.20 kg/m^3', 'DynamicViscosity': '1.80e-5 kg/m/s', 'MolarMass': '0.0289643897748887 kg/mol', 'Cp': '1004.703 J/kg/K', 'SutherlandConstant': '1.4579326545176254e-06 kg/m/s/K^0.5', 'SutherlandTemperature': '110.4 K'}

import CfdMeshRefinement
CfdMeshRefinement.makeCfdMeshRefinement(App.ActiveDocument.Box_Mesh)
referenceList = []
referenceList.append(('Box001','Face1'))
referenceList.append(('Box001','Face2'))
referenceList.append(('Box001','Face3'))
referenceList.append(('Box001','Face4'))
referenceList.append(('Box001','Face5'))
referenceList.append(('Box001','Face6'))
FreeCAD.ActiveDocument.MeshRefinement.References = referenceList

FreeCAD.ActiveDocument.MeshRefinement.RelativeLength = 0.75
FreeCAD.ActiveDocument.MeshRefinement.RefinementThickness = '0 mm'
FreeCAD.ActiveDocument.MeshRefinement.NumberLayers = 1
FreeCAD.ActiveDocument.MeshRefinement.ExpansionRatio = 1.2
FreeCAD.ActiveDocument.MeshRefinement.FirstLayerHeight = '0 mm'
FreeCAD.ActiveDocument.MeshRefinement.RegionEdgeRefinement = 1.0
FreeCAD.ActiveDocument.MeshRefinement.Internal = False

import CfdFluidBoundary
CfdTools.getActiveAnalysis().addObject(CfdFluidBoundary.makeCfdFluidBoundary())

bc = FreeCAD.ActiveDocument.CfdFluidBoundary
bc.BoundaryType = 'inlet'
bc.BoundarySubType = 'uniformVelocityInlet'
bc.ThermalBoundaryType = 'fixedValue'
bc.VelocityIsCartesian = True
bc.Ux = '0 mm/s'
bc.Uy = '0 mm/s'
bc.Uz = '1000 mm/s'
bc.VelocityMag = '0 mm/s'
bc.DirectionFace = ''
bc.ReverseNormal = True
bc.MassFlowRate = '0 kg/s'
bc.VolFlowRate = '0 mm^3/s'
bc.Pressure = '0 kg/(mm*s^2)'
bc.SlipRatio = '0 '
bc.Temperature = '293 K'
bc.HeatFlux = '0 kg/s^3'
bc.HeatTransferCoeff = '0 kg/(s^3*K)'
bc.TurbulentKineticEnergy = '10000 mm^2/s^2'
bc.SpecificDissipationRate = '57.3 deg/s'
bc.TurbulenceIntensity = '0.1 '
bc.TurbulenceLengthScale = '100 mm'
bc.PorousBaffleMethod = 'porousCoeff'
bc.PressureDropCoeff = '0 '
bc.ScreenWireDiameter = '0.1 mm'
bc.ScreenSpacing = '0 mm'
FreeCAD.ActiveDocument.CfdFluidBoundary.Label = 'inlet'
FreeCAD.ActiveDocument.CfdFluidBoundary.References = []
FreeCAD.ActiveDocument.CfdFluidBoundary.References.append(('Box', 'Face5'))
FreeCAD.ActiveDocument.recompute()

CfdTools.getActiveAnalysis().addObject(CfdFluidBoundary.makeCfdFluidBoundary())

bc = FreeCAD.ActiveDocument.CfdFluidBoundary001
bc.BoundaryType = 'outlet'
bc.BoundarySubType = 'staticPressureOutlet'
bc.ThermalBoundaryType = 'fixedValue'
bc.VelocityIsCartesian = True
bc.Ux = '0 mm/s'
bc.Uy = '0 mm/s'
bc.Uz = '0 mm/s'
bc.VelocityMag = '0 mm/s'
bc.DirectionFace = ''
bc.ReverseNormal = False
bc.MassFlowRate = '0 kg/s'
bc.VolFlowRate = '0 mm^3/s'
bc.Pressure = '0 kg/(mm*s^2)'
bc.SlipRatio = '0 '
bc.Temperature = '293 K'
bc.HeatFlux = '0 kg/s^3'
bc.HeatTransferCoeff = '0 kg/(s^3*K)'
bc.TurbulentKineticEnergy = '10000 mm^2/s^2'
bc.SpecificDissipationRate = '57.3 deg/s'
bc.TurbulenceIntensity = '0.1 '
bc.TurbulenceLengthScale = '100 mm'
bc.PorousBaffleMethod = 'porousCoeff'
bc.PressureDropCoeff = '0 '
bc.ScreenWireDiameter = '0.1 mm'
bc.ScreenSpacing = '0 mm'
FreeCAD.ActiveDocument.CfdFluidBoundary001.Label = 'outlet'
FreeCAD.ActiveDocument.CfdFluidBoundary001.References = []
FreeCAD.ActiveDocument.CfdFluidBoundary001.References.append(('Box', 'Face6'))
FreeCAD.ActiveDocument.recompute()

CfdTools.getActiveAnalysis().addObject(CfdFluidBoundary.makeCfdFluidBoundary())

bc = FreeCAD.ActiveDocument.CfdFluidBoundary002
bc.BoundaryType = 'wall'
bc.BoundarySubType = 'slipWall'
bc.ThermalBoundaryType = 'fixedValue'
bc.VelocityIsCartesian = True
bc.Ux = '0 mm/s'
bc.Uy = '0 mm/s'
bc.Uz = '0 mm/s'
bc.VelocityMag = '0 mm/s'
bc.DirectionFace = ''
bc.ReverseNormal = False
bc.MassFlowRate = '0 kg/s'
bc.VolFlowRate = '0 mm^3/s'
bc.Pressure = '0 kg/(mm*s^2)'
bc.SlipRatio = '0 '
bc.Temperature = '293 K'
bc.HeatFlux = '0 kg/s^3'
bc.HeatTransferCoeff = '0 kg/(s^3*K)'
bc.TurbulentKineticEnergy = '10000 mm^2/s^2'
bc.SpecificDissipationRate = '57.3 deg/s'
bc.TurbulenceIntensity = '0.1 '
bc.TurbulenceLengthScale = '100 mm'
bc.PorousBaffleMethod = 'porousCoeff'
bc.PressureDropCoeff = '0 '
bc.ScreenWireDiameter = '0.1 mm'
bc.ScreenSpacing = '0 mm'
FreeCAD.ActiveDocument.CfdFluidBoundary002.Label = 'wall'
FreeCAD.ActiveDocument.CfdFluidBoundary002.References = []
FreeCAD.ActiveDocument.CfdFluidBoundary002.References.append(('Box', 'Face4'))
FreeCAD.ActiveDocument.CfdFluidBoundary002.References.append(('Box', 'Face3'))
FreeCAD.ActiveDocument.CfdFluidBoundary002.References.append(('Box', 'Face2'))
FreeCAD.ActiveDocument.CfdFluidBoundary002.References.append(('Box', 'Face1'))
FreeCAD.ActiveDocument.recompute()

init = FreeCAD.ActiveDocument.InitialiseFields
init.PotentialFlow = True
init.Ux = '0 mm/s'
init.Uy = '0 mm/s'
init.Uz = '0 mm/s'
init.UseOutletPValue = True
init.BoundaryP = FreeCAD.ActiveDocument.CfdFluidBoundary001
init.Pressure = '0 kg/(mm*s^2)'
init.VolumeFractions = {}
init.Temperature = '293 K'
init.omega = '57.3 deg/s'
init.k = '0 mm^2/s^2'

import CfdZone
CfdTools.getActiveAnalysis().addObject(CfdZone.makeCfdPorousZone())
p = FreeCAD.ActiveDocument.PorousZone
p.PorousCorrelation = 'DarcyForchheimer'
p.D1 = '0 1/mm^2'
p.D2 = '0 1/mm^2'
p.D3 = '0 1/mm^2'
p.F1 = '0.001 1/mm'
p.F2 = '0.001 1/mm'
p.F3 = '0.001 1/mm'
p.e1 = (1.0, 0.0, 0.0)
p.e2 = (0.0, 1.0, 0.0)
p.e3 = (0.0, 0.0, 1.0)
p.OuterDiameter = '0 mm'
p.TubeAxis = (0.0, 0.0, 1.0 )
p.TubeSpacing = '0 mm'
p.SpacingDirection = (1.0, 0.0, 0.0)
p.AspectRatio = '1.73 '
p.VelocityEstimate = '0 mm/s'
FreeCAD.ActiveDocument.PorousZone.References = [('Box001', 'Solid1')]
