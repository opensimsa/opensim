# -*- coding: utf-8 -*-

# Macro Begin: /ntfs/projects/FreeCAD/macros/Falcon-boundaries-wall.FCMacro +++++++++++++++++++++++++++++++++++++++++++++++++
import FreeCAD
import _CommandCfdFluidBoundary
import CfdFluidBoundary
import FemGui

fb = CfdFluidBoundary.makeCfdFluidBoundary()
FemGui.getActiveAnalysis().addObject(fb)

# Values are converted to SI units and stored (eg. m/s)
bc = fb.BoundarySettings
bc['BoundaryType'] = 'wall'
bc['BoundarySubtype'] = 'fixed'
bc['ThermalBoundaryType'] = 'fixedValue'
bc['VelocityIsCartesian'] = True
bc['Ux'] = 0.0
bc['Uy'] = 0.0
bc['Uz'] = 0.0
bc['VelocityMag'] = 0.0
bc['DirectionFace'] = ''
bc['ReverseNormal'] = False
bc['MassFlowRate'] = 0.0
bc['VolFlowRate'] = 0.0
bc['Pressure'] = 0.0
bc['SlipRatio'] = 0.0
bc['TurbulenceInletSpecification'] = 'intensityAndLengthScale'
bc['TurbulentKineticEnergy'] = 0.01
bc['SpecificDissipationRate'] = 1.00007366139
bc['TurbulenceIntensity'] = 0.1
bc['TurbulenceLengthScale'] = 0.1
bc['PressureDropCoeff'] = 0.0
bc['ScreenWireDiameter'] = 0.0001
bc['ScreenSpacing'] = 0.0
bc['PorousBaffleMethod'] = 0
fb.BoundarySettings = bc
fb.Label = 'wall'
part = FreeCAD.ActiveDocument.getObject('Fusion')
for i, f in enumerate(part.Shape.Faces):
   fb.References.append((part.Name, 'Face{}'.format(i+1)))
FreeCAD.ActiveDocument.recompute()
# Macro End: /ntfs/projects/FreeCAD/macros/Falcon-boundaries-wall.FCMacro +++++++++++++++++++++++++++++++++++++++++++++++++s
