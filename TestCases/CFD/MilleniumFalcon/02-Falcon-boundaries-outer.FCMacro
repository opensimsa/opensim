# -*- coding: utf-8 -*-

# Macro Begin: /ntfs/projects/FreeCAD/macros/Falcon-boundaries.FCMacro +++++++++++++++++++++++++++++++++++++++++++++++++
import FreeCAD
import _CommandCfdFluidBoundary
import FemGui
import CfdFluidBoundary

#Gui.getDocument("Unnamed").getObject("Cut").Visibility=True
FemGui.getActiveAnalysis().addObject(CfdFluidBoundary.makeCfdFluidBoundary())

# Values are converted to SI units and stored (eg. m/s)
bc = FreeCAD.ActiveDocument.CfdFluidBoundary.BoundarySettings
bc['BoundaryType'] = 'inlet'
bc['BoundarySubtype'] = 'uniformVelocity'
bc['ThermalBoundaryType'] = 'fixedValue'
bc['VelocityIsCartesian'] = True
bc['Ux'] = 0.0
bc['Uy'] = 0.0
bc['Uz'] = -10.0
bc['VelocityMag'] = 0.0
bc['DirectionFace'] = 'Cut:Face3'
bc['ReverseNormal'] = False
bc['MassFlowRate'] = 0.0
bc['VolFlowRate'] = 0.0
bc['Pressure'] = 0.0
bc['SlipRatio'] = 0.0
bc['TurbulenceInletSpecification'] = 'intensityAndLengthScale'
bc['TurbulentKineticEnergy'] = 0.01
bc['SpecificDissipationRate'] = 1.00007366139
bc['TurbulenceIntensity'] = 0.1
bc['TurbulenceLengthScale'] = 0.1
bc['PressureDropCoeff'] = 0.0
bc['ScreenWireDiameter'] = 0.0001
bc['ScreenSpacing'] = 0.0
bc['PorousBaffleMethod'] = 0
FreeCAD.ActiveDocument.CfdFluidBoundary.BoundarySettings = bc
FreeCAD.ActiveDocument.CfdFluidBoundary.Label = 'inlet'
FreeCAD.ActiveDocument.CfdFluidBoundary.References.append(('XOR', 'Face3'))
FreeCAD.ActiveDocument.recompute()
FemGui.getActiveAnalysis().addObject(CfdFluidBoundary.makeCfdFluidBoundary())

# Values are converted to SI units and stored (eg. m/s)
bc = FreeCAD.ActiveDocument.CfdFluidBoundary001.BoundarySettings
bc['BoundaryType'] = 'wall'
bc['BoundarySubtype'] = 'slip'
bc['ThermalBoundaryType'] = 'fixedValue'
bc['VelocityIsCartesian'] = True
bc['Ux'] = 0.0
bc['Uy'] = 0.0
bc['Uz'] = 0.0
bc['VelocityMag'] = 0.0
bc['DirectionFace'] = 'XOR:Face1'
bc['ReverseNormal'] = False
bc['MassFlowRate'] = 0.0
bc['VolFlowRate'] = 0.0
bc['Pressure'] = 0.0
bc['SlipRatio'] = 0.0
bc['TurbulenceInletSpecification'] = 'intensityAndLengthScale'
bc['TurbulentKineticEnergy'] = 0.01
bc['SpecificDissipationRate'] = 1.00007366139
bc['TurbulenceIntensity'] = 0.1
bc['TurbulenceLengthScale'] = 0.1
bc['PressureDropCoeff'] = 0.0
bc['ScreenWireDiameter'] = 0.0001
bc['ScreenSpacing'] = 0.0
bc['PorousBaffleMethod'] = 0
FreeCAD.ActiveDocument.CfdFluidBoundary001.BoundarySettings = bc
FreeCAD.ActiveDocument.CfdFluidBoundary001.Label = 'outer'
FreeCAD.ActiveDocument.CfdFluidBoundary001.References.append(('XOR', 'Face1'))
FreeCAD.ActiveDocument.CfdFluidBoundary001.References.append(('XOR', 'Face4'))
FreeCAD.ActiveDocument.CfdFluidBoundary001.References.append(('XOR', 'Face6'))
FreeCAD.ActiveDocument.CfdFluidBoundary001.References.append(('XOR', 'Face2'))
FreeCAD.ActiveDocument.recompute()
FemGui.getActiveAnalysis().addObject(CfdFluidBoundary.makeCfdFluidBoundary())

# Values are converted to SI units and stored (eg. m/s)
bc = FreeCAD.ActiveDocument.CfdFluidBoundary002.BoundarySettings
bc['BoundaryType'] = 'outlet'
bc['BoundarySubtype'] = 'staticPressure'
bc['ThermalBoundaryType'] = 'fixedValue'
bc['VelocityIsCartesian'] = True
bc['Ux'] = 0.0
bc['Uy'] = 0.0
bc['Uz'] = 0.0
bc['VelocityMag'] = 0.0
bc['DirectionFace'] = 'XOR:Face5'
bc['ReverseNormal'] = False
bc['MassFlowRate'] = 0.0
bc['VolFlowRate'] = 0.0
bc['Pressure'] = 0.0
bc['SlipRatio'] = 0.0
bc['TurbulenceInletSpecification'] = 'intensityAndLengthScale'
bc['TurbulentKineticEnergy'] = 0.01
bc['SpecificDissipationRate'] = 1.00007366139
bc['TurbulenceIntensity'] = 0.1
bc['TurbulenceLengthScale'] = 0.1
bc['PressureDropCoeff'] = 0.0
bc['ScreenWireDiameter'] = 0.0001
bc['ScreenSpacing'] = 0.0
bc['PorousBaffleMethod'] = 0
FreeCAD.ActiveDocument.CfdFluidBoundary002.BoundarySettings = bc
FreeCAD.ActiveDocument.CfdFluidBoundary002.Label = 'outlet'
FreeCAD.ActiveDocument.CfdFluidBoundary002.References.append(('XOR', 'Face5'))
FreeCAD.ActiveDocument.recompute()
# Macro End: /ntfs/projects/FreeCAD/macros/Falcon-boundaries.FCMacro +++++++++++++++++++++++++++++++++++++++++++++++++
