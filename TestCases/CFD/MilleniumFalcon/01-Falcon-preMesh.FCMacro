# -*- coding: utf-8 -*-

# Macro Begin: /ntfs/projects/eskomFreeCAD/examples/training/Falcon.FCMacro +++++++++++++++++++++++++++++++++++++++++++++++++
import FreeCAD
import Part
import _CommandCfdAnalysis
import FemGui
import CfdAnalysis
import CfdPhysicsSelection
import CfdFluidMaterial
import CfdInitialiseFlowField
import CfdSolverFoam
import _CommandCfdMeshFromShape
import CfdMesh
import os

doc = App.newDocument()
Part.insert(os.path.join(os.path.dirname(__file__), "MillenniumFalcon_ANH_MasterModel_v1.1_150403_jm.STEP"),doc.Name)
App.activeDocument().addObject("Part::MultiFuse","Fusion")
App.activeDocument().Fusion.Shapes = [App.activeDocument().MillenniumFalcon_ANH_MasterModel_v1_1_150403_jm,App.activeDocument().MillenniumFalcon_ANH_MasterModel_v1_1_150403_jm001,]
#Gui.activeDocument().MillenniumFalcon_ANH_MasterModel_v1_1_150403_jm.Visibility=False
#Gui.activeDocument().MillenniumFalcon_ANH_MasterModel_v1_1_150403_jm001.Visibility=False
#Gui.ActiveDocument.Fusion.ShapeColor=Gui.ActiveDocument.MillenniumFalcon_ANH_MasterModel_v1_1_150403_jm.ShapeColor
#Gui.ActiveDocument.Fusion.DisplayMode=Gui.ActiveDocument.MillenniumFalcon_ANH_MasterModel_v1_1_150403_jm.DisplayMode
App.ActiveDocument.recompute()
App.ActiveDocument.addObject("Part::Box","Box")
App.ActiveDocument.ActiveObject.Label = "Cube"
App.ActiveDocument.recompute()
#Gui.SendMsgToActiveView("ViewFit")
#Gui.ActiveDocument.getObject("Fusion").Visibility=True
#Gui.ActiveDocument.getObject("Box").Visibility=True
App.ActiveDocument.getObject("Box").Length = '10000 mm'
App.ActiveDocument.getObject("Box").Width = '10000 mm'
App.ActiveDocument.getObject("Box").Height = '10000 mm'
App.ActiveDocument.getObject("Box").Placement = App.Placement(App.Vector(-5000,-5000,-5000),App.Rotation(App.Vector(0,0,1),0))
#Gui.ActiveDocument.getObject("Box").Visibility=False
#Gui.ActiveDocument.getObject("Box").Visibility=True
FreeCADGui.ActiveDocument.getObject("Box").Transparency = 50
Gui.activateWorkbench("PartWorkbench")
import BOPTools.SplitFeatures
j = BOPTools.SplitFeatures.makeXOR(name= 'XOR')
j.Objects = [App.ActiveDocument.Box, App.ActiveDocument.Fusion]
j.Proxy.execute(j)
j.purgeTouched()
for obj in j.ViewObject.Proxy.claimChildren():
    obj.ViewObject.hide()
#Gui.ActiveDocument.Cut.ShapeColor=Gui.ActiveDocument.Box.ShapeColor
#Gui.ActiveDocument.Cut.DisplayMode=Gui.ActiveDocument.Box.DisplayMode
App.ActiveDocument.recompute()
#Gui.ActiveDocument.setEdit('Cut',0)
#Gui.activateWorkbench("CfdOFWorkbench")
analysis = CfdAnalysis.makeCfdAnalysis('CfdAnalysis')
FemGui.setActiveAnalysis(analysis)
analysis.addObject(CfdPhysicsSelection.makeCfdPhysicsSelection())
phys = FreeCAD.ActiveDocument.PhysicsModel
phys.Time = 'Steady'
phys.Flow = 'Incompressible'
phys.Turbulence = 'RANS'
phys.TurbulenceModel = 'kOmegaSST'
phys.Thermal = 'None'
analysis.addObject(CfdFluidMaterial.makeCfdFluidMaterial('FluidProperties'))
analysis.addObject(CfdInitialiseFlowField.makeCfdInitialFlowField())
analysis.addObject(CfdSolverFoam.makeCfdSolverFoam())
CfdMesh.makeCfdMesh('Cut_Mesh')
App.ActiveDocument.ActiveObject.Part = App.ActiveDocument.XOR
FemGui.getActiveAnalysis().addObject(App.ActiveDocument.ActiveObject)

FreeCAD.ActiveDocument.Cut_Mesh.CharacteristicLengthMax = '0.5 m'
FreeCAD.ActiveDocument.Cut_Mesh.MeshUtility = 'cfMesh'
FreeCAD.ActiveDocument.Cut_Mesh.CellsBetweenLevels = 3
FreeCAD.ActiveDocument.Cut_Mesh.EdgeRefinement = 0
FreeCAD.ActiveDocument.Cut_Mesh.PointInMesh = {'y': 0.0, 'x': 0.0, 'z': 0.0}
# Macro End: /ntfs/projects/eskomFreeCAD/examples/training/Falcon.FCMacro +++++++++++++++++++++++++++++++++++++++++++++++++
