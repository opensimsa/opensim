# -*- coding: utf-8 -*-

# Macro Begin: /ntfs/projects/FreeCAD/macros/Falcon-meshRefine.FCMacro +++++++++++++++++++++++++++++++++++++++++++++++++
import FreeCAD
import CfdMeshRegion
import _CommandCfdMeshRegion

#Gui.ActiveDocument.getObject("Fusion").Visibility=True
#Gui.ActiveDocument.getObject("MillenniumFalcon_ANH_MasterModel_v1_1_150403_jm").Visibility=True
#Gui.ActiveDocument.getObject("MillenniumFalcon_ANH_MasterModel_v1_1_150403_jm001").Visibility=True
#Gui.ActiveDocument.getObject("Fusion").Visibility=False
#Gui.ActiveDocument.getObject("MillenniumFalcon_ANH_MasterModel_v1_1_150403_jm001").Visibility=False
#Gui.ActiveDocument.getObject("MillenniumFalcon_ANH_MasterModel_v1_1_150403_jm").Visibility=False
#Gui.ActiveDocument.getObject("MillenniumFalcon_ANH_MasterModel_v1_1_150403_jm001").Visibility=True
#Gui.ActiveDocument.getObject("MillenniumFalcon_ANH_MasterModel_v1_1_150403_jm").Visibility=True
#Gui.ActiveDocument.getObject("Fusion").Visibility=True
#Gui.ActiveDocument.getObject("MillenniumFalcon_ANH_MasterModel_v1_1_150403_jm").Visibility=False
#Gui.ActiveDocument.getObject("MillenniumFalcon_ANH_MasterModel_v1_1_150403_jm001").Visibility=False
CfdMeshRegion.makeCfdMeshRegion(App.ActiveDocument.Cut_Mesh)
#Gui.ActiveDocument.getObject("Cut").Visibility=False
FreeCADGui.ActiveDocument.getObject("Fusion").Transparency = 0
referenceList = []
part = FreeCAD.ActiveDocument.getObject('Fusion')
for i, f in enumerate(part.Shape.Faces):
    referenceList.append(('Fusion', 'Face{}'.format(i+1)))
FreeCAD.ActiveDocument.MeshRegion.References = referenceList

FreeCAD.ActiveDocument.MeshRegion.RelativeLength = 0.1
FreeCAD.ActiveDocument.MeshRegion.RefinementThickness = '0.1 m'
FreeCAD.ActiveDocument.MeshRegion.NumberLayers = 3
FreeCAD.ActiveDocument.MeshRegion.ExpansionRatio = 1.2
FreeCAD.ActiveDocument.MeshRegion.FirstLayerHeight = '0 mm'
FreeCAD.ActiveDocument.MeshRegion.RefinementLevel = 1
FreeCAD.ActiveDocument.MeshRegion.RegionEdgeRefinement = 1
FreeCAD.ActiveDocument.MeshRegion.Baffle = False
# Macro End: /ntfs/projects/FreeCAD/macros/Falcon-meshRefine.FCMacro +++++++++++++++++++++++++++++++++++++++++++++++++
